(defun C:AS (/ +_selection-filter+ _string-pos _appended-string _selected _entities _index _pickfirst-sysvar _old-error) 
  (setq _old-error *error*)

  ;; Состояния системных переменных
  ;; Для выбора объектов перед выполнением команды
  (setq _pickfirst-sysvar (getvar "PICKFIRST"))
  (if (= _pickfirst-sysvar 0) 
    (setvar "PICKFIRST" 1)
  )

  ;; -----------------
  ;; Восстановление изначального состояния
  ;; -----------------
  (defun _restore-state () 
    (setvar "PICKFIRST" _pickfirst-sysvar)
    (setq *error* _old-error)
  )

  ;; Установка обработчика ошибок
  (setq *error* _error-handler)

  ;; Получение выбранных объектов (многострочный текст, текст или блок)
  (setq +_selection-filter+ '((-4 . "<OR")
                              (0 . "TEXT")
                              (0 . "MTEXT")
                              (0 . "MULTILEADER")
                              (-4 . "<AND")
                              (0 . "INSERT")
                              (66 . 1)
                              (-4 . "AND>")
                              (-4 . "OR>")
                             )
        _selected           (ssget "_I" +_selection-filter+)
  )

  (setq _string-pos      (_getkword-initget "Положение строки" '("Начало" "Конец"))
        _appended-string (getstring T "Строка для дополнения: ")
        _entities        (if _selected 
                           _selected
                           (ssget +_selection-filter+)
                         )
  )
  (_loop-over-set 
    _entities
    (lambda (entity / _dxf-data) 
      (setq _dxf-data (entget entity))
      (if (= (_get-dxf 0 _dxf-data) "INSERT") 
        (setq _dxf-data (entget (entnext entity)))
      )

      (_append-text 
        _dxf-data
        (= _string-pos "Начало")
        _appended-string
      )
    )
  )

  ;; Восстановление изначальных настроек и состояния чертежа
  (_restore-state)

  (princ)
)
