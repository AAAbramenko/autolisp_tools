(defun C:DS (/ _selected _symb-numb +_selection-filter+ _pickfirst-sysvar _old-error) 
  (vl-load-com)

  (setq _old-error *error*)

  ;; Состояния системных переменных
  ;; Для выбора объектов перед выполнением команды
  (setq _pickfirst-sysvar (getvar "PICKFIRST"))
  (if (= _pickfirst-sysvar 0) 
    (setvar "PICKFIRST" 1)
  )

  ;; -----------------
  ;; Восстановление изначального состояния
  ;; -----------------
  (defun _restore-state () 
    (setvar "PICKFIRST" _pickfirst-sysvar)
    (setq *error* _old-error)
  )

  ;; Установка обработчика ошибок
  (setq *error* _error-handler)

  ;; Получение выбранных объектов (многострочный текст, текст или блок)
  (setq +_selection-filter+ '((-4 . "<OR")
                              (0 . "TEXT")
                              (0 . "MTEXT")
                              (0 . "MULTILEADER")
                              (-4 . "<AND")
                              (0 . "INSERT")
                              (66 . 1)
                              (-4 . "AND>")
                              (-4 . "OR>")
                             )
        _selected           (ssget "_I" +_selection-filter+)
  )

  (setq _delete-pos (_getkword-initget "Место удаления" '("Начало" "Конец")))
  (initget 6)
  (setq _symb-numb (getint "Количество символов для удаления: ")
        _entities  (if _selected 
                     _selected
                     (ssget +_selection-filter+)
                   )
  )

  ;; Проход по примитивам
  (_loop-over-set 
    _entities
    (lambda (entity) 
      (setq _dxf-data (entget 
                        ;; Выбор атрибута блока если первый выбранный объект блок
                        (if (= (cdr (assoc 0 (entget entity))) "INSERT") 
                          (entnext entity)
                          entity
                        )
                      )
      )

      (_delete-text-symb _dxf-data (= _delete-pos "Начало") _symb-numb)
    )
  )

  ;; Восстановление изначальных настроек и состояния чертежа
  (_restore-state)

  (princ)
)
